# Requirements for Etfuzel

# Specification: Specification Document
- Description: High Level Requirements

## ReqHL_01
The user can store so-called Mementos, which are objects that contain data that the user wants to remember

### ReqHL_Memento_01
Mementos may contain a description in the form of plain text

### ReqHL_Memento_02
Mementos may contain other elements, such as pictures, due dates...

## ReqHL_02
Memontos must be saved to persistent storage

### ReqHL_Storage_01
It must be possible to create a backup of the stored data

# Specification
- Description: User Interface Requirements

## ReqUI_01
A desktop application must be provided to manage mementos

### ReqUI_02
The user must be able to navigate to each of the available mementos

### ReqUI_03
After navigation to a memento, the contents shall be visualized

## ReqUI_100
The user interface must provide tools to store and load the mementos
